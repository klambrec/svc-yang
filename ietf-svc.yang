module ietf-svc {
  yang-version 1.1;
  namespace "urn:ietf:params:xml:ns:yang:ietf-svc";
  prefix svc;

  import ietf-inet-types {
    prefix inet;
  }
  import ietf-yang-types {
    prefix yang;
  }
  import ietf-netconf-acm {
    prefix nacm;
  }

  organization
    "IETF ONSEN Working Group";
  contact
    "Kris Lambrechts
     Email: kris@netedge.plus";
  description
    "This YANG module defines a generic base for service
     configuration models. This model is common across all
     vendor implementations.

     Copyright (c) 2026 IETF Trust and the persons
     identified as authors of the code.  All rights reserved.

     Redistribution and use in source and binary forms, with or
     without modification, is permitted pursuant to, and subject
     to the license terms contained in, the Simplified BSD License
     set forth in Section 4.c of the IETF Trust's Legal Provisions
     Relating to IETF Documents
     (https://trustee.ietf.org/license-info).";

  revision 2026-02-06 {
    description
      "Initial document.";
    reference
      "RFC XXXX";
  }

  feature site-diversity {
    description
      "Enables support of site diversity constraints.";
  }

  feature always-on {
    description
      "Enables support of the 'always-on' access constraint.";
  }

  feature requested-type {
    description
      "Enables support of the 'requested-type' access constraint.";
  }

  feature bearer-reference {
    description
      "Enables support of the 'bearer-reference' access constraint.";
  }

  feature qos {
    description
      "Enables support for QoS.";
  }

  feature qos-custom {
    description
      "Enables the support of a custom QoS profile.";
  }

  feature target-sites {
    description
      "Enables the support of the 'target-sites'
       match-flow parameter.";
  }

  feature input-bw {
    description
      "Enables the support of input bandwidth in a VPN.";
  }

  typedef svc-id {
    type string;
    description
      "Defines a type of service component identifier.";
  }

  typedef template-id {
    type string;
    description
      "Defines a type of service template identifier.";
  }

  typedef address-family {
    type enumeration {
      enum ipv4 {
        description
          "IPv4 address family.";
      }
      enum ipv6 {
        description
          "IPv6 address family.";
      }
    }
    description
      "Defines a type for the address family.";
  }

  identity site-network-access-type {
    description
      "Base identity for site-network-access type.";
  }

  identity point-to-point {
    base site-network-access-type;
    description
      "Identity for point-to-point connection.";
  }

  identity multipoint {
    base site-network-access-type;
    description
      "Identity for multipoint connection.
       Example: Ethernet broadcast segment.";
  }

  identity placement-diversity {
    description
      "Base identity for site placement constraints.";
  }

  identity bearer-diverse {
    base placement-diversity;
    description
      "Identity for bearer diversity.
       The bearers should not use common elements.";
  }

  identity pe-diverse {
    base placement-diversity;
    description
      "Identity for PE diversity.";
  }

  identity pop-diverse {
    base placement-diversity;
    description
      "Identity for POP diversity.";
  }

  identity linecard-diverse {
    base placement-diversity;
    description
      "Identity for linecard diversity.";
  }

  identity same-pe {
    base placement-diversity;
    description
      "Identity for having sites connected on the same PE.";
  }

  identity same-bearer {
    base placement-diversity;
    description
      "Identity for having sites connected using the same bearer.";
  }

  identity management {
    description
      "Base identity for site management scheme.";
  }

  identity co-managed {
    base management;
    description
      "Base identity for co-managed site.";
  }

  identity customer-managed {
    base management;
    description
      "Base identity for customer-managed site.";
  }

  identity provider-managed {
    base management;
    description
      "Base identity for provider-managed site.";
  }

  identity policing {
    description
      "Identity of the type of policing applied.";
  }

  identity one-rate-two-color {
    base policing;
    description
      "Identity of one-rate, two-color (1R2C).";
  }

  identity two-rate-three-color {
    base policing;
    description
      "Identity of two-rate, three-color (2R3C).";
  }

  identity qos-profile-direction {
    description
      "Base identity for the QoS-profile direction.";
  }

  identity site-to-wan {
    base qos-profile-direction;
    description
      "Identity for the site-to-WAN direction.";
  }

  identity wan-to-site {
    base qos-profile-direction;
    description
      "Identity for the WAN-to-site direction.";
  }

  identity bidirectional {
    base qos-profile-direction;
    description
      "Identity for both the WAN-to-site direction
       and the site-to-WAN direction.";
  }

  identity bw-type {
    description
      "Identity of the bandwidth type.";
  }

  identity bw-per-cos {
    base bw-type;
    description
      "Bandwidth is per CoS.";
  }

  identity bw-per-port {
    base bw-type;
    description
      "Bandwidth is per site network access.";
  }

  identity bw-per-site {
    base bw-type;
    description
      "Bandwidth is per site.  It is applicable to
       all the site network accesses within the site.";
  }

  identity bw-per-svc {
    base bw-type;
    description
      "Bandwidth is per VPN service.";
  }

  identity bw-direction {
    description
      "Identity for the bandwidth direction.";
  }

  identity input-bw {
    base bw-direction;
    description
      "Identity for the input bandwidth.";
  }

  identity output-bw {
    base bw-direction;
    description
      "Identity for the output bandwidth.";
  }

  identity color-type {
    description
      "Identity of color types.";
  }

  identity green {
    base color-type;
    description
      "Identity of the 'green' color type.";
  }

  identity yellow {
    base color-type;
    description
      "Identity of the 'yellow' color type.";
  }

  identity red {
    base color-type;
    description
      "Identity of the 'red' color type.";
  }

  identity customer-application {
    description
      "Base identity for a customer application.";
  }

  identity web {
    base customer-application;
    description
      "Identity for a web application (e.g., HTTP, HTTPS).";
  }

  identity mail {
    base customer-application;
    description
      "Identity for a mail application.";
  }

  identity file-transfer {
    base customer-application;
    description
      "Identity for a file-transfer application
       (e.g., FTP, SFTP).";
  }

  identity database {
    base customer-application;
    description
      "Identity for a database application.";
  }

  identity social {
    base customer-application;
    description
      "Identity for a social-network application.";
  }

  identity games {
    base customer-application;
    description
      "Identity for a gaming application.";
  }

  identity p2p {
    base customer-application;
    description
      "Identity for a peer-to-peer application.";
  }

  identity network-management {
    base customer-application;
    description
      "Identity for a management application
       (e.g., Telnet, syslog, SNMP).";
  }

  identity voice {
    base customer-application;
    description
      "Identity for a voice application.";
  }

  identity video {
    base customer-application;
    description
      "Identity for a videoconference application.";
  }

  identity embb {
    base customer-application;
    description
      "Identity for the enhanced Mobile Broadband (eMBB)
       application.  Note that the eMBB application
       requires strict threshold values for a wide variety
       of network performance parameters (e.g., data rate,
       latency, loss rate, reliability).";
  }

  identity urllc {
    base customer-application;
    description
      "Identity for the Ultra-Reliable and Low Latency
       Communications (URLLC) application.  Note that the
       URLLC application requires strict threshold values for
       a wide variety of network performance parameters
       (e.g., latency, reliability).";
  }

  identity mmtc {
    base customer-application;
    description
      "Identity for the massive Machine Type
       Communications (mMTC) application.  Note that the
       mMTC application requires strict threshold values for
       a wide variety of network performance parameters
       (e.g., data rate, latency, loss rate, reliability).";
  }

  grouping customer-location-info {
    container locations {
      list location {
        key "location-id";
        leaf location-id {
          type svc-id;
          description
            "Identifier for a particular location.";
        }
        leaf address {
          type string;
          description
            "Address (number and street) of the site.";
        }
        leaf postal-code {
          type string;
          description
            "Postal code of the site.";
        }
        leaf state {
          type string;
          description
            "State of the site.  This leaf can also be
             used to describe a region for a country that
             does not have states.";
        }
        leaf city {
          type string;
          description
            "City of the site.";
        }
        leaf country-code {
          type string {
            pattern '[A-Z]{2}';
          }
          description
            "Country of the site.
             Expressed as ISO ALPHA-2 code.";
        }
        description
          "Location of the site.";
      }
      description
        "List of locations for the site.";
    }
    description
      "This grouping defines customer location parameters.";
  }

  grouping site-group {
    container groups {
      list group {
        key "group-id";
        leaf group-id {
          type string;
          description
            "Group-id the site belongs to.";
        }
        description
          "List of group-ids.";
      }
      description
        "Groups the site or site-network-access belongs to.";
    }
    description
      "Grouping definition to assign
       group-ids to site or site-network-access.";
  }

  grouping site-diversity {
    container site-diversity {
      if-feature "site-diversity";
      uses site-group;
      description
        "Diversity constraint type.  All
         site-network-accesses will inherit
         the group values defined here.";
    }
    description
      "This grouping defines site
       diversity parameters.";
  }

  grouping site-service-qos-profile {
    container qos {
      if-feature "qos";
      container qos-classification-policy {
        list rule {
          key "id";
          ordered-by user;
          leaf id {
            type string;
            description
              "A description identifying the QoS classification
               policy rule.";
          }
          choice match-type {
            default "match-flow";
            case match-flow {
              container match-flow {
                leaf dscp {
                  type inet:dscp;
                  description
                    "DSCP value.";
                }
                leaf dot1q {
                  type uint16;
                  description
                    "802.1Q matching.  It is a VLAN tag added into
                     a frame.";
                }
                leaf pcp {
                  type uint8 {
                    range "0..7";
                  }
                  description
                    "PCP value.";
                }
                leaf color-type {
                  type identityref {
                    base color-type;
                  }
                  description
                    "Color types.";
                }
                leaf-list target-sites {
                  if-feature "target-sites";
                  type svc:svc-id;
                  description
                    "Identifies a site as a traffic destination.";
                }
                leaf any {
                  type empty;
                  description
                    "Allow all.";
                }
                leaf vpn-id {
                  type svc:svc-id;
                  description
                    "Reference to the target VPN.";
                }
                description
                  "Describes flow-matching criteria.";
              }
            }
            case match-application {
              leaf match-application {
                type identityref {
                  base customer-application;
                }
                description
                  "Defines the application to match.";
              }
            }
            description
              "Choice for classification.";
          }
          leaf target-class-id {
            type string;
            description
              "Identification of the CoS.
               This identifier is internal to the
               administration.";
          }
          description
            "List of marking rules.";
        }
        description
          "Configuration of the traffic classification policy.";
      }
      container qos-profile {
        choice qos-profile {
          description
            "Choice for the QoS profile.
             Can be a standard profile or a customized profile.";
          case standard {
            description
              "Standard QoS profile.";
            leaf profile {
              type leafref {
                path "/svc:svc/svc:svc-profiles/"
                   + "svc:valid-provider-identifiers/"
                   + "svc:qos-profile-identifier/svc:id";
              }
              description
                "QoS profile to be used.";
            }
          }
          case custom {
            description
              "Customized QoS profile.";
            container classes {
              if-feature "qos-custom";
              list class {
                key "class-id";
                leaf class-id {
                  type string;
                  description
                    "Identification of the CoS.  This identifier is
                     internal to the administration.";
                }
                leaf direction {
                  type identityref {
                    base qos-profile-direction;
                  }
                  default "bidirectional";
                  description
                    "The direction in which the QoS profile is
                     applied.  By default, the direction is
                     bidirectional.";
                }
                leaf policing {
                  type identityref {
                    base policing;
                  }
                  default "one-rate-two-color";
                  description
                    "The policing type can be either one-rate,
                     two-color (1R2C) or two-rate, three-color
                     (2R3C).  By default, the policing type is
                     'one-rate-two-color'.";
                }
                leaf byte-offset {
                  type uint16;
                  description
                    "Number of bytes in the service frame header
                     that are excluded from the QoS calculation
                     (e.g., extra VLAN tags).";
                }
                container frame-delay {
                  choice flavor {
                    case lowest {
                      leaf use-lowest-latency {
                        type empty;
                        description
                          "The traffic class should use the path
                           with the lowest delay.";
                      }
                    }
                    case boundary {
                      leaf delay-bound {
                        type uint16;
                        units "milliseconds";
                        description
                          "The traffic class should use a path
                           with a defined maximum delay.";
                      }
                    }
                    description
                      "Delay constraint on the traffic class.";
                  }
                  description
                    "Delay constraint on the traffic class.";
                }
                container frame-jitter {
                  choice flavor {
                    case lowest {
                      leaf use-lowest-jitter {
                        type empty;
                        description
                          "The traffic class should use the path
                           with the lowest jitter.";
                      }
                    }
                    case boundary {
                      leaf delay-bound {
                        type uint32;
                        units "microseconds";
                        description
                          "The traffic class should use a path
                           with a defined maximum jitter.";
                      }
                    }
                    description
                      "Jitter constraint on the traffic class.";
                  }
                  description
                    "Jitter constraint on the traffic class.";
                }
                container frame-loss {
                  leaf rate {
                    type decimal64 {
                      fraction-digits 2;
                      range "0..100";
                    }
                    units "percent";
                    description
                      "Frame loss rate constraint on the traffic
                       class.";
                  }
                  description
                    "Container for frame loss rate.";
                }
                container bandwidth {
                  leaf guaranteed-bw-percent {
                    type decimal64 {
                      fraction-digits 5;
                      range "0..100";
                    }
                    units "percent";
                    mandatory true;
                    description
                      "Used to define the guaranteed bandwidth
                       as a percentage of the available service
                       bandwidth.";
                  }
                  leaf end-to-end {
                    type empty;
                    description
                      "Used if the bandwidth reservation
                       must be done on the MPLS network too.";
                  }
                  description
                    "Bandwidth constraint on the traffic class.";
                }
                description
                  "List of CoS entries.";
              }
              description
                "Container for list of CoS entries.";
            }
          }
        }
        description
          "QoS profile configuration.";
      }
      description
        "QoS configuration.";
    }
    description
      "Grouping that defines QoS parameters for a site.";
  }

  grouping access-diversity {
    container access-diversity {
      if-feature "site-diversity";
      uses site-group;
      container constraints {
        list constraint {
          key "constraint-type";
          leaf constraint-type {
            type identityref {
              base placement-diversity;
            }
            description
              "Diversity constraint type.";
          }
          container target {
            choice target-flavor {
              default "id";
              case id {
                list group {
                  key "group-id";
                  leaf group-id {
                    type string;
                    description
                      "The constraint will be applied against
                       this particular group-id for this site
                       network access level.";
                  }
                  description
                    "List of group-ids associated with one specific
                     constraint for this site network access level.";
                }
              }
              case all-accesses {
                leaf all-other-accesses {
                  type empty;
                  description
                    "The constraint will be applied against
                     all other site network accesses of this site.";
                }
              }
              case all-groups {
                leaf all-other-groups {
                  type empty;
                  description
                    "The constraint will be applied against
                     all other groups managed by the customer.";
                }
              }
              description
                "Choice for the target flavor definition.";
            }
            description
              "The constraint will be applied against a
               Specific target, and the target can be a list
               of group-ids,all other site network accesses of
               this site, or all other groups managed by the
               customer.";
          }
          description
            "List of constraints.";
        }
        description
          "Placement constraints for this site network access.";
      }
      description
        "Diversity parameters.";
    }
    description
      "This grouping defines access diversity parameters.";
  }

  grouping operational-requirements {
    leaf requested-site-start {
      type yang:date-and-time;
      description
        "Optional leaf indicating requested date and
         time when the service at a particular site is
         expected to start.";
    }
    leaf requested-site-stop {
      type yang:date-and-time;
      description
        "Optional leaf indicating requested date and
         time when the service at a particular site is
         expected to stop.";
    }
    description
      "This grouping defines some operational
       parameters.";
  }

  grouping operational-requirements-ops {
    leaf actual-site-start {
      type yang:date-and-time;
      config false;
      description
        "Optional leaf indicating actual date and
         time when the service at a particular site
         actually started.";
    }
    leaf actual-site-stop {
      type yang:date-and-time;
      config false;
      description
        "Optional leaf indicating actual date and
         time when the service at a particular site
         actually stopped.";
    }
    description
      "This grouping defines some operational
       parameters.";
  }

  grouping site-attachment-bearer {
    container bearer {
      container requested-type {
        if-feature "requested-type";
        leaf requested-type {
          type string;
          description
            "Type of requested bearer: Ethernet, DSL,
             Wireless, etc. Operator specific.";
        }
        leaf strict {
          type boolean;
          default "false";
          description
            "Defines whether requested-type is a preference
             or a strict requirement.";
        }
        description
          "Container for requested-type.";
      }
      leaf always-on {
        if-feature "always-on";
        type boolean;
        default "true";
        description
          "Request for an always-on access type.
           For example, this could mean no dial access type.";
      }
      leaf bearer-reference {
        if-feature "bearer-reference";
        type string;
        description
          "This is an internal reference for the SP.";
      }
      description
        "Bearer-specific parameters.
         To be augmented.";
    }
    description
      "Defines physical properties of a site attachment.";
  }

  grouping site-management {
    container management {
      leaf type {
        type identityref {
          base management;
        }
        mandatory true;
        description
          "Management type of the connection.";
      }
      description
        "Management configuration.";
    }
    description
      "Management parameters for the site.";
  }

  grouping site-devices {
    container devices {
      when
        "derived-from-or-self(../management/type, "
      + "'svc:provider-managed') or "
      + "derived-from-or-self(../management/type, 'svc:co-managed')" {
        description
          "Applicable only for provider-managed or
           co-managed device.";
      }
      list device {
        key "device-id";
        leaf device-id {
          type svc-id;
          description
            "Identifier for the device.";
        }
        leaf location {
          type leafref {
            path "../../../locations/"
               + "location/location-id";
          }
          mandatory true;
          description
            "Location of the device.";
        }
        container management {
          when "derived-from-or-self(../../../management/type,"
             + "'svc:co-managed')" {
            description
              "Applicable only for co-managed device.";
          }
          leaf address-family {
            type address-family;
            description
              "Address family used for management.";
          }
          leaf address {
            when '(../address-family)' {
              description
                "If address-family is specified, then address should
                 also be specified.  If address-family is not specified,
                 then address should also not be specified.";
            }
            type inet:ip-address;
            mandatory true;
            description
              "Management address.";
          }
          description
            "Management configuration.  Applicable only for
             co-managed device.";
        }
        description
          "List of devices requested by customer.";
      }
      description
        "Device configuration.";
    }
    description
      "Grouping for device allocation.";
  }

  grouping site-attachment-availability {
    container availability {
      leaf access-priority {
        type uint32;
        default "100";
        description
          "Defines the priority for the access.
           The higher the access-priority value,
           the higher the preference of the
           access will be.";
      }
      description
        "Availability parameters (used for multihoming).";
    }
    description
      "Defines availability parameters for a site.";
  }

  grouping site-top-level-cfg {
    uses operational-requirements;
    uses customer-location-info;
    uses site-devices;
    uses site-diversity;
    uses site-management;
    container service {
      uses site-service-qos-profile;
      description
        "Container for services.";
    }
    description
      "Grouping for site top-level configuration.";
  }

  grouping site-network-access-top-level-cfg {
    leaf site-network-access-type {
      type identityref {
        base site-network-access-type;
      }
      default "point-to-point";
      description
        "Describes the type of connection, e.g.,
         point-to-point or multipoint.";
    }
    choice location-flavor {
      case location {
        when "derived-from-or-self(../../management/type, "
           + "'svc:customer-managed')" {
          description
            "Applicable only for customer-managed device.";
        }
        leaf location-reference {
          type leafref {
            path "../../../locations/location/location-id";
          }
          description
            "Location of the site-network-access.";
        }
      }
      case device {
        when "derived-from-or-self(../../management/type, "
           + "'svc:provider-managed') or "
           + "derived-from-or-self(../../management/type, "
           + "'svc:co-managed')" {
          description
            "Applicable only for provider-managed or co-managed device.";
        }
        leaf device-reference {
          type leafref {
            path "../../../devices/device/device-id";
          }
          description
            "Identifier of CE to use.";
        }
      }
      mandatory true;
      description
        "Choice of how to describe the site's location.";
    }
    uses access-diversity;
    uses site-attachment-bearer;
    uses site-attachment-availability;
    container service {
      container svc-bandwidth {
        if-feature "input-bw";
        list bandwidth {
          key "direction type";
          leaf direction {
            type identityref {
              base bw-direction;
            }
            description
              "Indicates the bandwidth direction.  It can be
               the bandwidth download direction from the SP to
               the site or the bandwidth upload direction from
               the site to the SP.";
          }
          leaf type {
            type identityref {
              base bw-type;
            }
            description
              "Bandwidth type.  By default, the bandwidth type
               is set to 'bw-per-cos'.";
          }
          leaf cos-id {
            when "derived-from-or-self(../type, "
               + "'svc:bw-per-cos')" {
              description
                "Relevant when the bandwidth type is set to
                 'bw-per-cos'.";
            }
            type uint8;
            description
              "Identifier of the CoS, indicated by DSCP or a
               CE-VLAN CoS (802.1p) value in the service frame.
               If the bandwidth type is set to 'bw-per-cos',
               the CoS ID MUST also be specified.";
          }
          leaf vpn-id {
            when "derived-from-or-self(../type, "
               + "'svc:bw-per-svc')" {
              description
                "Relevant when the bandwidth type is
                 set as bandwidth per VPN service.";
            }
            type svc:svc-id;
            description
              "Identifies the target VPN.  If the bandwidth
               type is set as bandwidth per VPN service, the
               vpn-id MUST be specified.";
          }
          leaf cir {
            type uint64;
            units "bps";
            mandatory true;
            description
              "Committed Information Rate.  The maximum number
               of bits that a port can receive or send over
               an interface in one second.";
          }
          leaf cbs {
            type uint64;
            units "bps";
            mandatory true;
            description
              "Committed Burst Size (CBS).  Controls the bursty
               nature of the traffic.  Traffic that does not
               use the configured Committed Information Rate
               (CIR) accumulates credits until the credits
               reach the configured CBS.";
          }
          leaf eir {
            type uint64;
            units "bps";
            description
              "Excess Information Rate (EIR), i.e., excess frame
               delivery allowed that is not subject to an SLA.
               The traffic rate can be limited by the EIR.";
          }
          leaf ebs {
            type uint64;
            units "bps";
            description
              "Excess Burst Size (EBS).  The bandwidth available
               for burst traffic from the EBS is subject to the
               amount of bandwidth that is accumulated during
               periods when traffic allocated by the EIR
               policy is not used.";
          }
          leaf pir {
            type uint64;
            units "bps";
            description
              "Peak Information Rate, i.e., maximum frame
               delivery allowed.  It is equal to or less
               than the sum of the CIR and the EIR.";
          }
          leaf pbs {
            type uint64;
            units "bps";
            description
              "Peak Burst Size.  It is measured in bytes per
               second.";
          }
          description
            "List of bandwidth values (e.g., per CoS,
             per vpn-id).";
        }
        description
          "From the customer site's perspective, the service
           input/output bandwidth of the connection or
           download/upload bandwidth from the SP/site
           to the site/SP.";
      }
      leaf svc-mtu {
        type uint16;
        units "bytes";
        description
          "SVC MTU.  It is also known as the maximum
           transmission unit or maximum frame size.  When
           a frame is larger than the MTU, it is broken
           down, or fragmented, into smaller pieces by
           the network protocol to accommodate the MTU
           of the network.  If CsC is enabled,
           the requested svc-mtu leaf will refer to the
           MPLS MTU and not to the link MTU.";
      }
      uses site-service-qos-profile;
      description
        "Container for services.";
    }
    description
      "Grouping for site network access top-level configuration.";
  }

  container svc {
    container svc-profiles {
      container valid-provider-identifiers {
        list qos-profile-identifier {
          key "id";
          leaf id {
            type string;
            description
              "Identification of the QoS Profile to be used.
               Local administration meaning.";
          }
          description
            "List for QoS Profile Identifiers.";
        }
        list bfd-profile-identifier {
          key "id";
          leaf id {
            type string;
            description
              "Identification of the SP BFD Profile to be used.
               Local administration meaning.";
          }
          description
            "List for BFD Profile identifiers.";
        }
        nacm:default-deny-write;
        description
          "Container for Valid Provider Identifies.";
      }
      description
        "Container for Service Profiles.";
    }
    container sites {
      list site {
        key "site-id";
        leaf site-id {
          type svc-id;
          description
            "Identifier of the site.";
        }
        uses site-top-level-cfg;
        uses operational-requirements-ops;
        container site-network-accesses {
          list site-network-access {
            key "site-network-access-id";
            leaf site-network-access-id {
              type svc-id;
              description
                "Identifier for the access.";
            }
            uses site-network-access-top-level-cfg;
            description
              "List of accesses for a site.";
          }
          description
            "Container for accesses for a site.";
        }
        description
          "List of sites.";
      }
      description
        "Container for sites.";
    }
    description
      "Main container for service configuration.";
  }
}
