module ietf-l3vpn-svc {
  yang-version 1.1;
  namespace "urn:ietf:params:xml:ns:yang:ietf-l3vpn-svc";
  prefix l3vpn-svc;

  import ietf-inet-types {
    prefix inet;
  }
  import ietf-yang-types {
    prefix yang;
  }
  import ietf-svc {
    prefix svc;
  }
  import ietf-vpn-svc {
    prefix vpn-svc;
  }

  organization
    "IETF ONSEN Working Group";
  contact
    "Kris Lambrechts
     Email: kris@netedge.plus";
  description
    "This YANG module defines a generic service configuration
     model for Layer 3 VPNs. This model is common across all
     vendor implementations.

     Copyright (c) 2026 IETF Trust and the persons
     identified as authors of the code.  All rights reserved.

     Redistribution and use in source and binary forms, with or
     without modification, is permitted pursuant to, and subject
     to the license terms contained in, the Simplified BSD License
     set forth in Section 4.c of the IETF Trust's Legal Provisions
     Relating to IETF Documents
     (https://trustee.ietf.org/license-info).";

  revision 2026-02-06 {
    description
      "Revision of RFC 8299 to enable a shared service model.";
    reference
      "RFC XXXX";
  }
  revision 2018-01-19 {
    description
      "Revision of RFC 8049 to fix implementation issues.";
    reference
      "RFC 8299";
  }
  revision 2017-01-27 {
    description
      "Initial document.";
    reference
      "RFC 8049.";
  }

  feature multicast {
    description
      "Enables multicast capabilities in a VPN.";
  }

  feature ipv4 {
    description
      "Enables IPv4 support in a VPN.";
  }

  feature ipv6 {
    description
      "Enables IPv6 support in a VPN.";
  }

  feature extranet-vpn {
    description
      "Enables support of extranet VPNs.";
  }

  feature encryption {
    description
      "Enables support of encryption.";
  }

  feature rtg-bgp {
    description
      "Enables support of the BGP routing protocol.";
  }

  feature rtg-rip {
    description
      "Enables support of the RIP routing protocol.";
  }

  feature rtg-ospf {
    description
      "Enables support of the OSPF routing protocol.";
  }

  feature rtg-ospf-sham-link {
    description
      "Enables support of OSPF sham links.";
  }

  feature rtg-vrrp {
    description
      "Enables support of the VRRP routing protocol.";
  }

  feature fast-reroute {
    description
      "Enables support of Fast Reroute.";
  }

  feature bfd {
    description
      "Enables support of BFD.";
  }

  typedef template-id {
    type string;
    description
      "Defines a type of service template identifier.";
  }

  identity site-vpn-flavor-sub {
    base vpn-svc:site-vpn-flavor;
    description
      "Base identity for the site VPN service flavor.
       Used when a site has multiple logical connections.
       Each connection may belong to different multiple VPNs.";
  }

  identity address-allocation-type {
    description
      "Base identity for address-allocation-type for PE-CE link.";
  }

  identity provider-dhcp {
    base address-allocation-type;
    description
      "Provider network provides DHCP service to customer.";
  }

  identity provider-dhcp-relay {
    base address-allocation-type;
    description
      "Provider network provides DHCP relay service to customer.";
  }

  identity provider-dhcp-slaac {
    base address-allocation-type;
    description
      "Provider network provides DHCP service to customer,
       as well as SLAAC.";
  }

  identity static-address {
    base address-allocation-type;
    description
      "Provider-to-customer addressing is static.";
  }

  identity slaac {
    base address-allocation-type;
    description
      "Use IPv6 SLAAC.";
  }

  identity multicast-tree-type {
    description
      "Base identity for multicast tree type.";
  }

  identity ssm-tree-type {
    base multicast-tree-type;
    description
      "Identity for SSM tree type.";
  }

  identity asm-tree-type {
    base multicast-tree-type;
    description
      "Identity for ASM tree type.";
  }

  identity bidir-tree-type {
    base multicast-tree-type;
    description
      "Identity for bidirectional tree type.";
  }

  identity multicast-rp-discovery-type {
    description
      "Base identity for RP discovery type.";
  }

  identity auto-rp {
    base multicast-rp-discovery-type;
    description
      "Base identity for Auto-RP discovery type.";
  }

  identity static-rp {
    base multicast-rp-discovery-type;
    description
      "Base identity for static type.";
  }

  identity bsr-rp {
    base multicast-rp-discovery-type;
    description
      "Base identity for BSR discovery type.";
  }

  identity routing-protocol-type {
    description
      "Base identity for routing protocol type.";
  }

  identity ospf {
    base routing-protocol-type;
    description
      "Identity for OSPF protocol type.";
  }

  identity bgp {
    base routing-protocol-type;
    description
      "Identity for BGP protocol type.";
  }

  identity static {
    base routing-protocol-type;
    description
      "Identity for static routing protocol type.";
  }

  identity rip {
    base routing-protocol-type;
    description
      "Identity for RIP protocol type.";
  }

  identity vrrp {
    base routing-protocol-type;
    description
      "Identity for VRRP protocol type.
       This is to be used when LANs are directly connected
       to PE routers.";
  }

  identity direct {
    base routing-protocol-type;
    description
      "Identity for direct protocol type.";
  }

  identity protocol-type {
    description
      "Base identity for protocol field type.";
  }

  identity tcp {
    base protocol-type;
    description
      "TCP protocol type.";
  }

  identity udp {
    base protocol-type;
    description
      "UDP protocol type.";
  }

  identity icmp {
    base protocol-type;
    description
      "ICMP protocol type.";
  }

  identity icmp6 {
    base protocol-type;
    description
      "ICMPv6 protocol type.";
  }

  identity gre {
    base protocol-type;
    description
      "GRE protocol type.";
  }

  identity ipip {
    base protocol-type;
    description
      "IP-in-IP protocol type.";
  }

  identity hop-by-hop {
    base protocol-type;
    description
      "Hop-by-Hop IPv6 header type.";
  }

  identity routing {
    base protocol-type;
    description
      "Routing IPv6 header type.";
  }

  identity esp {
    base protocol-type;
    description
      "ESP header type.";
  }

  identity ah {
    base protocol-type;
    description
      "AH header type.";
  }

  identity ipv4 {
    base vpn-svc:vpn-policy-filter-type;
    description
      "Identity for IPv4 Prefix filter type.";
  }

  identity ipv6 {
    base vpn-svc:vpn-policy-filter-type;
    description
      "Identity for IPv6 Prefix filter type.";
  }

  grouping multicast-rp-group-cfg {
    choice group-format {
      mandatory true;
      case singleaddress {
        leaf group-address {
          type inet:ip-address;
          description
            "A single multicast group address.";
        }
      }
      case startend {
        leaf group-start {
          type inet:ip-address;
          description
            "The first multicast group address in
             the multicast group address range.";
        }
        leaf group-end {
          type inet:ip-address;
          description
            "The last multicast group address in
             the multicast group address range.";
        }
      }
      description
        "Choice for multicast group format.";
    }
    description
      "This grouping defines multicast group or
       multicast groups for RP-to-group mapping.";
  }

  grouping vpn-service-multicast {
    container multicast {
      if-feature "multicast";
      leaf enabled {
        type boolean;
        default "false";
        description
          "Enables multicast.";
      }
      container customer-tree-flavors {
        leaf-list tree-flavor {
          type identityref {
            base multicast-tree-type;
          }
          description
            "Type of tree to be used.";
        }
        description
          "Type of trees used by customer.";
      }
      container rp {
        container rp-group-mappings {
          list rp-group-mapping {
            key "id";
            leaf id {
              type uint16;
              description
                "Unique identifier for the mapping.";
            }
            container provider-managed {
              leaf enabled {
                type boolean;
                default "false";
                description
                  "Set to true if the Rendezvous Point (RP)
                   must be a provider-managed node.  Set to false
                   if it is a customer-managed node.";
              }
              leaf rp-redundancy {
                type boolean;
                default "false";
                description
                  "If true, a redundancy mechanism for the RP
                   is required.";
              }
              leaf optimal-traffic-delivery {
                type boolean;
                default "false";
                description
                  "If true, the SP must ensure that
                   traffic uses an optimal path.  An SP may use
                   Anycast RP or RP-tree-to-SPT switchover
                   architectures.";
              }
              description
                "Parameters for a provider-managed RP.";
            }
            leaf rp-address {
              when "../provider-managed/enabled = 'false'" {
                description
                  "Relevant when the RP is not provider-managed.";
              }
              type inet:ip-address;
              mandatory true;
              description
                "Defines the address of the RP.
                 Used if the RP is customer-managed.";
            }
            container groups {
              list group {
                key "id";
                leaf id {
                  type uint16;
                  description
                    "Identifier for the group.";
                }
                uses multicast-rp-group-cfg;
                description
                  "List of multicast groups.";
              }
              description
                "Multicast groups associated with the RP.";
            }
            description
              "List of RP-to-group mappings.";
          }
          description
            "RP-to-group mappings parameters.";
        }
        container rp-discovery {
          leaf rp-discovery-type {
            type identityref {
              base multicast-rp-discovery-type;
            }
            default "static-rp";
            description
              "Type of RP discovery used.";
          }
          container bsr-candidates {
            when "derived-from-or-self(../rp-discovery-type, "
               + "'l3vpn-svc:bsr-rp')" {
              description
                "Only applicable if discovery type
                 is BSR-RP.";
            }
            leaf-list bsr-candidate-address {
              type inet:ip-address;
              description
                "Address of BSR candidate.";
            }
            description
              "Container for List of Customer
               BSR candidate's addresses.";
          }
          description
            "RP discovery parameters.";
        }
        description
          "RP parameters.";
      }
      description
        "Multicast global parameters for the VPN service.";
    }
    description
      "Grouping for multicast VPN definition.";
  }

  grouping flow-definition {
    leaf ipv4-src-prefix {
      type inet:ipv4-prefix;
      description
        "Match on IPv4 src address.";
    }
    leaf ipv6-src-prefix {
      type inet:ipv6-prefix;
      description
        "Match on IPv6 src address.";
    }
    leaf ipv4-dst-prefix {
      type inet:ipv4-prefix;
      description
        "Match on IPv4 dst address.";
    }
    leaf ipv6-dst-prefix {
      type inet:ipv6-prefix;
      description
        "Match on IPv6 dst address.";
    }
    leaf l4-src-port {
      type inet:port-number;
      must 'current() < ../l4-src-port-range/lower-port or '
         + 'current() > ../l4-src-port-range/upper-port' {
        description
          "If l4-src-port and l4-src-port-range/lower-port and
            upper-port are set at the same time, l4-src-port
            should not overlap with l4-src-port-range.";
      }
      description
        "Match on Layer 4 src port.";
    }
    container l4-src-port-range {
      leaf lower-port {
        type inet:port-number;
        description
          "Lower boundary for port.";
      }
      leaf upper-port {
        type inet:port-number;
        must '. >= ../lower-port' {
          description
            "Upper boundary for port.  If it
              exists, the upper boundary must be
              higher than the lower boundary.";
        }
        description
          "Upper boundary for port.";
      }
      description
        "Match on Layer 4 src port range.  When
          only the lower-port is present, it represents
          a single port.  When both the lower-port and
          upper-port are specified, it implies
          a range inclusive of both values.";
    }
    leaf l4-dst-port {
      type inet:port-number;
      must 'current() < ../l4-dst-port-range/lower-port or '
         + 'current() > ../l4-dst-port-range/upper-port' {
        description
          "If l4-dst-port and l4-dst-port-range/lower-port
            and upper-port are set at the same time,
            l4-dst-port should not overlap with
            l4-src-port-range.";
      }
      description
        "Match on Layer 4 dst port.";
    }
    container l4-dst-port-range {
      leaf lower-port {
        type inet:port-number;
        description
          "Lower boundary for port.";
      }
      leaf upper-port {
        type inet:port-number;
        must '. >= ../lower-port' {
          description
            "Upper boundary must be
              higher than lower boundary.";
        }
        description
          "Upper boundary for port.  If it exists,
            upper boundary must be higher than lower
            boundary.";
      }
      description
        "Match on Layer 4 dst port range.  When only
          lower-port is present, it represents a single
          port.  When both lower-port and upper-port are
          specified, it implies a range inclusive of both
          values.";
    }
    leaf protocol-field {
      type union {
        type uint8;
        type identityref {
          base protocol-type;
        }
      }
      description
        "Match on IPv4 protocol or IPv6 Next Header field.";
    }
    description
      "Flow definition based on criteria.";
  }

  grouping site-protection {
    container traffic-protection {
      if-feature "fast-reroute";
      leaf enabled {
        type boolean;
        default "false";
        description
          "Enables traffic protection of access link.";
      }
      description
        "Fast Reroute service parameters for the site.";
    }
    description
      "Defines protection service parameters for a site.";
  }

  grouping site-security-authentication {
    container authentication {
      description
        "Authentication parameters.";
    }
    description
      "This grouping defines authentication parameters for a site.";
  }

  grouping site-security-encryption {
    container encryption {
      if-feature "encryption";
      leaf enabled {
        type boolean;
        default "false";
        description
          "If true, traffic encryption on the connection is required.";
      }
      leaf layer {
        when "../enabled = 'true'" {
          description
            "Require a value for layer when enabled is true.";
        }
        type enumeration {
          enum layer2 {
            description
              "Encryption will occur at Layer 2.";
          }
          enum layer3 {
            description
              "Encryption will occur at Layer 3.
               For example, IPsec may be used when
               a customer requests Layer 3 encryption.";
          }
        }
        description
          "Layer on which encryption is applied.";
      }
      container encryption-profile {
        choice profile {
          case provider-profile {
            leaf profile-name {
              type leafref {
                path
                  "/svc:svc/svc:svc-profiles/svc:valid-provider-identifiers"
                + "/encryption-profile-identifier/id";
              }
              description
                "Name of the SP profile to be applied.";
            }
          }
          case customer-profile {
            leaf algorithm {
              type string;
              description
                "Encryption algorithm to be used.";
            }
            choice key-type {
              default "psk";
              case psk {
                leaf preshared-key {
                  type string;
                  description
                    "Pre-Shared Key (PSK) coming from the customer.";
                }
              }
              description
                "Type of keys to be used.";
            }
          }
          description
            "Choice of encryption profile.  The encryption
             profile can be the provider profile or customer profile.";
        }
        description
          "Profile of encryption to be applied.";
      }
      description
        "Encryption parameters.";
    }
    description
      "This grouping defines encryption parameters for a site.";
  }

  grouping site-routing {
    container routing-protocols {
      list routing-protocol {
        key "type";
        leaf type {
          type identityref {
            base routing-protocol-type;
          }
          description
            "Type of routing protocol.";
        }
        container ospf {
          when "derived-from-or-self(../type, 'l3vpn-svc:ospf')" {
            description
              "Only applies when protocol is OSPF.";
          }
          if-feature "rtg-ospf";
          leaf-list address-family {
            type svc:address-family;
            min-elements 1;
            description
              "If OSPF is used on this site, this node
               contains a configured value.  This node
               contains at least one address family
               to be activated.";
          }
          leaf area-address {
            type yang:dotted-quad;
            mandatory true;
            description
              "Area address.";
          }
          leaf metric {
            type uint16;
            default "1";
            description
              "Metric of the PE-CE link.  It is used
               in the routing state calculation and
               path selection.";
          }
          container sham-links {
            if-feature "rtg-ospf-sham-link";
            list sham-link {
              key "target-site";
              leaf target-site {
                type svc:svc-id;
                description
                  "Target site for the sham link connection.
                   The site is referred to by its ID.";
              }
              leaf metric {
                type uint16;
                default "1";
                description
                  "Metric of the sham link.  It is used in
                   the routing state calculation and path
                   selection.  The default value is set
                   to 1.";
              }
              description
                "Creates a sham link with another site.";
            }
            description
              "List of sham links.";
          }
          description
            "OSPF-specific configuration.";
        }
        container bgp {
          when "derived-from-or-self(../type, 'l3vpn-svc:bgp')" {
            description
              "Only applies when protocol is BGP.";
          }
          if-feature "rtg-bgp";
          leaf autonomous-system {
            type uint32;
            mandatory true;
            description
              "Customer AS number in case the customer
               requests BGP routing.";
          }
          leaf-list address-family {
            type svc:address-family;
            min-elements 1;
            description
              "If BGP is used on this site, this node
               contains a configured value.  This node
               contains at least one address family
               to be activated.";
          }
          description
            "BGP-specific configuration.";
        }
        container static {
          when "derived-from-or-self(../type, 'l3vpn-svc:static')" {
            description
              "Only applies when protocol is static.
               BGP activation requires the SP to know
               the address of the customer peer.  When
               BGP is enabled, the 'static-address'
               allocation type for the IP connection
               MUST be used.";
          }
          container cascaded-lan-prefixes {
            list ipv4-lan-prefixes {
              if-feature "ipv4";
              key "lan next-hop";
              leaf lan {
                type inet:ipv4-prefix;
                description
                  "LAN prefixes.";
              }
              leaf lan-tag {
                type string;
                description
                  "Internal tag to be used in VPN policies.";
              }
              leaf next-hop {
                type inet:ipv4-address;
                description
                  "Next-hop address to use on the customer side.";
              }
              description
                "List of LAN prefixes for the site.";
            }
            list ipv6-lan-prefixes {
              if-feature "ipv6";
              key "lan next-hop";
              leaf lan {
                type inet:ipv6-prefix;
                description
                  "LAN prefixes.";
              }
              leaf lan-tag {
                type string;
                description
                  "Internal tag to be used in VPN policies.";
              }
              leaf next-hop {
                type inet:ipv6-address;
                description
                  "Next-hop address to use on the customer side.";
              }
              description
                "List of LAN prefixes for the site.";
            }
            description
              "LAN prefixes from the customer.";
          }
          description
            "Configuration specific to static routing.";
        }
        container rip {
          when "derived-from-or-self(../type, 'l3vpn-svc:rip')" {
            description
              "Only applies when the protocol is RIP.  For IPv4,
               the model assumes that RIP version 2 is used.";
          }
          if-feature "rtg-rip";
          leaf-list address-family {
            type svc:address-family;
            min-elements 1;
            description
              "If RIP is used on this site, this node
               contains a configured value.  This node
               contains at least one address family
               to be activated.";
          }
          description
            "Configuration specific to RIP routing.";
        }
        container vrrp {
          when "derived-from-or-self(../type, 'l3vpn-svc:vrrp')" {
            description
              "Only applies when protocol is VRRP.";
          }
          if-feature "rtg-vrrp";
          leaf-list address-family {
            type svc:address-family;
            min-elements 1;
            description
              "If VRRP is used on this site, this node
               contains a configured value.  This node contains
               at least one address family to be activated.";
          }
          description
            "Configuration specific to VRRP routing.";
        }
        description
          "List of routing protocols used on
           the site.  This list can be augmented.";
      }
      description
        "Defines routing protocols.";
    }
    description
      "Grouping for routing protocols.";
  }

  grouping site-attachment-ip-connection {
    container ip-connection {
      container ipv4 {
        if-feature "ipv4";
        leaf address-allocation-type {
          type identityref {
            base address-allocation-type;
          }
          must
            "not(derived-from-or-self(current(), 'l3vpn-svc:slaac') or "
          + "derived-from-or-self(current(), "
          + "'l3vpn-svc:provider-dhcp-slaac'))" {
            error-message "SLAAC is only applicable to IPv6";
          }
          description
            "Defines how addresses are allocated.
             If there is no value for the address
             allocation type, then IPv4 is not enabled.";
        }
        container provider-dhcp {
          when "derived-from-or-self(../address-allocation-type, "
             + "'l3vpn-svc:provider-dhcp')" {
            description
              "Only applies when addresses are allocated by DHCP.";
          }
          leaf provider-address {
            type inet:ipv4-address;
            description
              "Address of provider side.  If provider-address is not
               specified, then prefix length should not be specified
               either.  It also implies provider-dhcp allocation is
               not enabled.  If provider-address is specified, then
               the prefix length may or may not be specified.";
          }
          leaf prefix-length {
            type uint8 {
              range "0..32";
            }
            must '(../provider-address)' {
              error-message
                "If the prefix length is specified, provider-address
                 must also be specified.";
              description
                "If the prefix length is specified, provider-address
                 must also be specified.";
            }
            description
              "Subnet prefix length expressed in bits.
               If not specified, or specified as zero,
               this means the customer leaves the actual
               prefix length value to the provider.";
          }
          choice address-assign {
            default "number";
            case number {
              leaf number-of-dynamic-address {
                type uint16;
                default "1";
                description
                  "Describes the number of IP addresses
                   the customer requires.";
              }
            }
            case explicit {
              container customer-addresses {
                list address-group {
                  key "group-id";
                  leaf group-id {
                    type string;
                    description
                      "Group-id for the address range from
                       start-address to end-address.";
                  }
                  leaf start-address {
                    type inet:ipv4-address;
                    description
                      "First address.";
                  }
                  leaf end-address {
                    type inet:ipv4-address;
                    description
                      "Last address.";
                  }
                  description
                    "Describes IP addresses allocated by DHCP.
                     When only start-address or only end-address
                     is present, it represents a single address.
                     When both start-address and end-address are
                     specified, it implies a range inclusive of both
                     addresses.  If no address is specified, it implies
                     customer addresses group is not supported.";
                }
                description
                  "Container for customer addresses is allocated by DHCP.";
              }
            }
            description
              "Choice for the way to assign addresses.";
          }
          description
            "DHCP allocated addresses related parameters.";
        }
        container dhcp-relay {
          when "derived-from-or-self(../address-allocation-type, "
             + "'l3vpn-svc:provider-dhcp-relay')" {
            description
              "Only applies when provider is required to implement
               DHCP relay function.";
          }
          leaf provider-address {
            type inet:ipv4-address;
            description
              "Address of provider side.  If provider-address is not
               specified, then prefix length should not be specified
               either.  It also implies provider-dhcp allocation is
               not enabled.  If provider-address is specified, then
               prefix length may or may not be specified.";
          }
          leaf prefix-length {
            type uint8 {
              range "0..32";
            }
            must '(../provider-address)' {
              error-message
                "If prefix length is specified, provider-address
                 must also be specified.";
              description
                "If prefix length is specified, provider-address
                 must also be specified.";
            }
            description
              "Subnet prefix length expressed in bits.  If not
               specified, or specified as zero, this means the
               customer leaves the actual prefix length value
               to the provider.";
          }
          container customer-dhcp-servers {
            leaf-list server-ip-address {
              type inet:ipv4-address;
              description
                "IP address of customer DHCP server.";
            }
            description
              "Container for list of customer DHCP servers.";
          }
          description
            "DHCP relay provided by operator.";
        }
        container addresses {
          when "derived-from-or-self(../address-allocation-type, "
             + "'l3vpn-svc:static-address')" {
            description
              "Only applies when protocol allocation type is static.";
          }
          leaf provider-address {
            type inet:ipv4-address;
            description
              "IPv4 Address List of the provider side.
               When the protocol allocation type is static,
               the provider address must be configured.";
          }
          leaf customer-address {
            type inet:ipv4-address;
            description
              "IPv4 Address of customer side.";
          }
          leaf prefix-length {
            type uint8 {
              range "0..32";
            }
            description
              "Subnet prefix length expressed in bits.
               It is applied to both provider-address
               and customer-address.";
          }
          description
            "Describes IPv4 addresses used.";
        }
        description
          "IPv4-specific parameters.";
      }
      container ipv6 {
        if-feature "ipv6";
        leaf address-allocation-type {
          type identityref {
            base address-allocation-type;
          }
          description
            "Defines how addresses are allocated.
             If there is no value for the address
             allocation type, then IPv6 is
             not enabled.";
        }
        container provider-dhcp {
          when
            "derived-from-or-self(../address-allocation-type, "
          + "'l3vpn-svc:provider-dhcp') "
          + "or derived-from-or-self(../address-allocation-type, "
          + "'l3vpn-svc:provider-dhcp-slaac')" {
            description
              "Only applies when addresses are allocated by DHCP.";
          }
          leaf provider-address {
            type inet:ipv6-address;
            description
              "Address of the provider side.  If provider-address
               is not specified, then prefix length should not be
               specified either.  It also implies provider-dhcp
               allocation is not enabled.  If provider-address is
               specified, then prefix length may or may
               not be specified.";
          }
          leaf prefix-length {
            type uint8 {
              range "0..128";
            }
            must '(../provider-address)' {
              error-message
                "If prefix length is specified, provider-address
                 must also be specified.";
              description
                "If prefix length is specified, provider-address
                 must also be specified.";
            }
            description
              "Subnet prefix length expressed in bits.  If not
               specified, or specified as zero, this means the
               customer leaves the actual prefix length value
               to the provider.";
          }
          choice address-assign {
            default "number";
            case number {
              leaf number-of-dynamic-address {
                type uint16;
                default "1";
                description
                  "Describes the number of IP addresses the customer
                   requires.";
              }
            }
            case explicit {
              container customer-addresses {
                list address-group {
                  key "group-id";
                  leaf group-id {
                    type string;
                    description
                      "Group-id for the address range from
                       start-address to end-address.";
                  }
                  leaf start-address {
                    type inet:ipv6-address;
                    description
                      "First address.";
                  }
                  leaf end-address {
                    type inet:ipv6-address;
                    description
                      "Last address.";
                  }
                  description
                    "Describes IP addresses allocated by DHCP.  When only
                     start-address or only end-address is present, it
                     represents a single address.  When both start-address
                     and end-address are specified, it implies a range
                     inclusive of both addresses.  If no address is
                     specified, it implies customer addresses group is
                     not supported.";
                }
                description
                  "Container for customer addresses allocated by DHCP.";
              }
            }
            description
              "Choice for the way to assign addresses.";
          }
          description
            "DHCP allocated addresses related parameters.";
        }
        container dhcp-relay {
          when "derived-from-or-self(../address-allocation-type, "
             + "'l3vpn-svc:provider-dhcp-relay')" {
            description
              "Only applies when the provider is required
               to implement DHCP relay function.";
          }
          leaf provider-address {
            type inet:ipv6-address;
            description
              "Address of the provider side.  If provider-address is
               not specified, then prefix length should not be
               specified either.  It also implies provider-dhcp
               allocation is not enabled.  If provider address
               is specified, then prefix length may or may
               not be specified.";
          }
          leaf prefix-length {
            type uint8 {
              range "0..128";
            }
            must '(../provider-address)' {
              error-message
                "If prefix length is specified, provider-address
                 must also be specified.";
              description
                "If prefix length is specified, provider-address
                 must also be specified.";
            }
            description
              "Subnet prefix length expressed in bits.  If not
               specified, or specified as zero, this means the
               customer leaves the actual prefix length value
               to the provider.";
          }
          container customer-dhcp-servers {
            leaf-list server-ip-address {
              type inet:ipv6-address;
              description
                "This node contains the IP address of
                 the customer DHCP server.  If the DHCP relay
                 function is implemented by the
                 provider, this node contains the
                 configured value.";
            }
            description
              "Container for list of customer DHCP servers.";
          }
          description
            "DHCP relay provided by operator.";
        }
        container addresses {
          when "derived-from-or-self(../address-allocation-type, "
             + "'l3vpn-svc:static-address')" {
            description
              "Only applies when protocol allocation type is static.";
          }
          leaf provider-address {
            type inet:ipv6-address;
            description
              "IPv6 Address of the provider side.  When the protocol
               allocation type is static, the provider address
               must be configured.";
          }
          leaf customer-address {
            type inet:ipv6-address;
            description
              "The IPv6 Address of the customer side.";
          }
          leaf prefix-length {
            type uint8 {
              range "0..128";
            }
            description
              "Subnet prefix length expressed in bits.
               It is applied to both provider-address and
               customer-address.";
          }
          description
            "Describes IPv6 addresses used.";
        }
        description
          "IPv6-specific parameters.";
      }
      container oam {
        container bfd {
          if-feature "bfd";
          leaf enabled {
            type boolean;
            default "false";
            description
              "If true, BFD activation is required.";
          }
          choice holdtime {
            default "fixed";
            case fixed {
              leaf fixed-value {
                type uint32;
                units "msec";
                description
                  "Expected BFD holdtime expressed in msec.  The customer
                   may impose some fixed values for the holdtime period
                   if the provider allows the customer use this function.
                   If the provider doesn't allow the customer to use this
                   function, the fixed-value will not be set.";
              }
            }
            case profile {
              leaf profile-name {
                type leafref {
                  path
                    "/svc:svc/svc:svc-profiles/svc:valid-provider-identifiers/"
                  + "svc:bfd-profile-identifier/svc:id";
                }
                description
                  "Well-known SP profile name.  The provider can propose
                   some profiles to the customer, depending on the service
                   level the customer wants to achieve.  Profile names
                   must be communicated to the customer.";
              }
              description
                "Well-known SP profile.";
            }
            description
              "Choice for holdtime flavor.";
          }
          description
            "Container for BFD.";
        }
        description
          "Defines the Operations, Administration, and Maintenance (OAM)
           mechanisms used on the connection.  BFD is set as a fault
           detection mechanism, but the 'oam' container can easily
           be augmented by other mechanisms";
      }
      description
        "Defines connection parameters.";
    }
    description
      "This grouping defines IP connection parameters.";
  }

  grouping site-service-multicast {
    container multicast {
      if-feature "multicast";
      leaf multicast-site-type {
        type enumeration {
          enum receiver-only {
            description
              "The site only has receivers.";
          }
          enum source-only {
            description
              "The site only has sources.";
          }
          enum source-receiver {
            description
              "The site has both sources and receivers.";
          }
        }
        default "source-receiver";
        description
          "Type of multicast site.";
      }
      container multicast-address-family {
        leaf ipv4 {
          if-feature "ipv4";
          type boolean;
          default "false";
          description
            "Enables IPv4 multicast.";
        }
        leaf ipv6 {
          if-feature "ipv6";
          type boolean;
          default "false";
          description
            "Enables IPv6 multicast.";
        }
        description
          "Defines protocol to carry multicast.";
      }
      leaf protocol-type {
        type enumeration {
          enum host {
            description
              "Hosts are directly connected to the provider network.
               Host protocols such as IGMP or MLD are required.";
          }
          enum router {
            description
              "Hosts are behind a customer router.
               PIM will be implemented.";
          }
          enum both {
            description
              "Some hosts are behind a customer router, and
               some others are directly connected to the
               provider network.  Both host and routing protocols
               must be used.  Typically, IGMP and PIM will be
               implemented.";
          }
        }
        default "both";
        description
          "Multicast protocol type to be used with the customer site.";
      }
      description
        "Multicast parameters for the site.";
    }
    description
      "Multicast parameters for the site.";
  }

  grouping site-maximum-routes {
    container maximum-routes {
      list address-family {
        key "af";
        leaf af {
          type svc:address-family;
          description
            "Address family.";
        }
        leaf maximum-routes {
          type uint32;
          description
            "Maximum prefixes the VRF can accept
             for this address family.";
        }
        description
          "List of address families.";
      }
      description
        "Defines 'maximum-routes' for the VRF.";
    }
    description
      "Defines 'maximum-routes' for the site.";
  }

  grouping site-security {
    container security {
      uses site-security-authentication;
      uses site-security-encryption;
      description
        "Site-specific security parameters.";
    }
    description
      "Grouping for security parameters.";
  }

  grouping site-top-level-cfg {
    uses site-maximum-routes;
    uses site-security;
    uses site-protection;
    uses site-routing;
    description
      "Grouping for site top-level configuration.";
  }

  grouping site-network-access-top-level-cfg {
    uses site-attachment-ip-connection;
    uses site-security;
    uses site-routing;
    description
      "Grouping for site network access top-level configuration.";
  }

  augment "/svc:svc/svc:svc-profiles"
        + "/svc:valid-provider-identifiers" {
    list encryption-profile-identifier {
      key "id";
      leaf id {
        type string;
        description
          "Identification of the SP encryption profile
            to be used.  Local administration meaning.";
      }
      description
        "List for encryption profile identifiers.";
    }
  }

  augment "/svc:svc/vpn-svc:vpn-services/vpn-svc:vpn-service" {
    uses vpn-service-multicast;
    description
      "Augmentation for VPN service configuration.";
  }

  augment "/svc:svc/vpn-svc:vpn-services/vpn-svc:vpn-service"
        + "/vpn-svc:cloud-accesses/vpn-svc:cloud-access" {
    container address-translation {
      container nat44 {
        leaf enabled {
          type boolean;
          default "false";
          description
            "Controls whether or not Network address
             translation from IPv4 to IPv4 (NAT44)
             [RFC3022] is required.";
        }
        leaf nat44-customer-address {
          type inet:ipv4-address;
          description
            "Address to be used for network address
             translation from IPv4 to IPv4.  This is
             to be used if the customer is providing
             the IPv4 address.  If the customer address
             is not set, the model assumes that the
             provider will allocate the address.";
        }
        description
          "IPv4-to-IPv4 translation.";
      }
      description
        "Container for NAT.";
    }
  }

  augment "/svc:svc/svc:sites/svc:site" {
    uses site-top-level-cfg;
  }

  augment "/svc:svc/svc:sites/svc:site/vpn-svc:vpn-policies"
        + "/vpn-svc:vpn-policy/vpn-svc:entries/vpn-svc:filters"
        + "/vpn-svc:filter" {
    leaf-list ipv4-lan-prefix {
      when
        "derived-from-or-self(../vpn-svc:type, 'l3vpn-svc:ipv4')" {
        description
          "Only applies when VPN Policy filter is IPv4 Prefix filter.";
      }
      if-feature "ipv4";
      type inet:ipv4-prefix;
      description
        "List of IPv4 prefixes as LAN Prefixes to be matched.";
    }
    leaf-list ipv6-lan-prefix {
      when
        "derived-from-or-self(../vpn-svc:type, 'l3vpn-svc:ipv6')" {
        description
          "Only applies when VPN Policy filter is IPv6 Prefix filter.";
      }
      if-feature "ipv6";
      type inet:ipv6-prefix;
      description
        "List of IPv6 prefixes as LAN prefixes to be matched.";
    }
    description
      "List of filters used on the site.  This list can
        be augmented.";
  }

  augment "/svc:svc/svc:sites/svc:site/svc:service" {
    uses site-service-multicast;
  }

  augment "/svc:svc/svc:sites/svc:site/svc:service"
        + "/svc:qos/svc:qos-classification-policy"
        + "/svc:rule/svc:match-type/svc:match-flow"
        + "/svc:match-flow" {
    uses flow-definition;
  }

  augment "/svc:svc/svc:sites/svc:site/svc:site-network-accesses"
        + "/svc:site-network-access" {
    uses site-network-access-top-level-cfg;
  }

  augment "/svc:svc/svc:sites/svc:site/svc:site-network-accesses"
        + "/svc:site-network-access/svc:service" {
    uses site-service-multicast;
  }

  augment "/svc:svc/svc:sites/svc:site/svc:site-network-accesses"
        + "/svc:site-network-access/svc:service/svc:qos"
        + "/svc:qos-classification-policy/svc:rule"
        + "/svc:match-type/svc:match-flow"
        + "/svc:match-flow" {
    uses flow-definition;
  }
}
