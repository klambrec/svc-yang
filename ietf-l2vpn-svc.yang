module ietf-l2vpn-svc {
  yang-version 1.1;
  namespace "urn:ietf:params:xml:ns:yang:ietf-l2vpn-svc";
  prefix l2vpn-svc;

  import ietf-inet-types {
    prefix inet;
  }
  import ietf-yang-types {
    prefix yang;
  }
  import ietf-svc {
    prefix svc;
  }
  import ietf-vpn-svc {
    prefix vpn-svc;
  }

  organization
    "IETF ONSEN Working Group.";
  contact
    "Kris Lambrechts
     Email: kris@netedge.plus";
  description
    "This YANG module defines a generic service configuration model
     for Layer 2 VPN services common across all vendor
     implementations.

     Copyright (c) 2026 IETF Trust and the persons
     identified as authors of the code.  All rights reserved.

     Redistribution and use in source and binary forms, with or
     without modification, is permitted pursuant to, and subject
     to the license terms contained in, the Simplified BSD License
     set forth in Section 4.c of the IETF Trust's Legal Provisions
     Relating to IETF Documents
     (https://trustee.ietf.org/license-info).";

  revision 2026-02-06 {
    description
      "Revision of RFC 8466 to enable a shared service model.";
    reference
      "RFC XXXX";
  }
  revision 2018-10-09 {
    description
      "Initial revision.";
    reference
      "RFC 8466: A YANG Data Model for Layer 2 Virtual Private
       Network (L2VPN) Service Delivery";
  }

  feature ethernet-oam {
    description
      "Enables the support of Ethernet Service OAM.";
  }

  feature l2cp-control {
    description
      "Enables the support of L2CP control.";
  }

  feature output-bw {
    description
      "Enables the support of output bandwidth in a VPN.";
  }

  feature uni-list {
    description
      "Enables the support of a list of UNIs in a VPN.";
  }

  feature oam-3ah {
    description
      "Enables the support of OAM 802.3ah.";
  }

  feature micro-bfd {
    description
      "Enables the support of micro-BFD.";
  }

  feature bfd {
    description
      "Enables the support of BFD.";
  }

  feature signaling-options {
    description
      "Enables the support of signaling options.";
  }

  feature encryption {
    description
      "Enables the support of encryption.";
  }

  feature lag-interface {
    description
      "Enables LAG interfaces.";
  }

  feature vlan {
    description
      "Enables the support of VLANs.";
  }

  feature dot1q {
    description
      "Enables the support of dot1Q.";
  }

  feature qinq {
    description
      "Enables the support of QinQ.";
  }

  feature qinany {
    description
      "Enables the support of QinAny.";
  }

  feature vxlan {
    description
      "Enables the support of VXLANs.";
  }

  feature bum {
    description
      "Enables BUM capabilities in a VPN.";
  }

  feature mac-loop-prevention {
    description
      "Enables the MAC loop-prevention capability in a VPN.";
  }

  feature lacp {
    description
      "Enables the Link Aggregation Control Protocol (LACP)
       capability in a VPN.";
  }

  feature mac-addr-limit {
    description
      "Enables the MAC address limit capability in a VPN.";
  }

  feature acl {
    description
      "Enables the ACL capability in a VPN.";
  }

  feature cfm {
    description
      "Enables the 802.1ag CFM capability in a VPN.";
  }

  feature y-1731 {
    description
      "Enables the Y.1731 capability in a VPN.";
  }

  typedef ccm-priority-type {
    type uint8 {
      range "0..7";
    }
    description
      "A 3-bit priority value to be used in the VLAN tag,
       if present in the transmitted frame.";
  }

  typedef control-mode {
    type enumeration {
      enum peer {
        description
          "'peer' mode, i.e., participate in the protocol towards
           the CE.  Peering is common for LACP and the Ethernet
           Local Management Interface (E-LMI) and, occasionally,
           for LLDP.  For VPLSs and VPWSs, the subscriber can also
           request that the SP peer enable spanning tree.";
      }
      enum tunnel {
        description
          "'tunnel' mode, i.e., pass to the egress or destination
           site.  For EPLs, the expectation is that L2CP frames are
           tunneled.";
      }
      enum discard {
        description
          "'discard' mode, i.e., discard the frame.";
      }
    }
    description
      "Defines the type of control mode on L2CP protocols.";
  }

  typedef neg-mode {
    type enumeration {
      enum full-duplex {
        description
          "Defines full-duplex mode.";
      }
      enum auto-neg {
        description
          "Defines auto-negotiation mode.";
      }
    }
    description
      "Defines the type of negotiation mode.";
  }

  identity tag-type {
    description
      "Base identity from which all tag types are derived.";
  }

  identity c-vlan {
    base tag-type;
    description
      "A CVLAN tag, normally using the 0x8100 Ethertype.";
  }

  identity s-vlan {
    base tag-type;
    description
      "An SVLAN tag.";
  }

  identity c-s-vlan {
    base tag-type;
    description
      "Using both a CVLAN tag and an SVLAN tag.";
  }

  identity multicast-tree-type {
    description
      "Base identity for the multicast tree type.";
  }

  identity ssm-tree-type {
    base multicast-tree-type;
    description
      "Identity for the Source-Specific Multicast (SSM) tree type.";
    reference
      "RFC 8299: YANG Data Model for L3VPN Service Delivery";
  }

  identity asm-tree-type {
    base multicast-tree-type;
    description
      "Identity for the Any-Source Multicast (ASM) tree type.";
    reference
      "RFC 8299: YANG Data Model for L3VPN Service Delivery";
  }

  identity bidir-tree-type {
    base multicast-tree-type;
    description
      "Identity for the bidirectional tree type.";
    reference
      "RFC 8299: YANG Data Model for L3VPN Service Delivery";
  }

  identity multicast-gp-address-mapping {
    description
      "Identity for mapping type.";
  }

  identity static-mapping {
    base multicast-gp-address-mapping;
    description
      "Identity for static mapping, i.e., attach the interface
       to the multicast group as a static member.";
  }

  identity dynamic-mapping {
    base multicast-gp-address-mapping;
    description
      "Identity for dynamic mapping, i.e., an interface was added
       to the multicast group as a result of snooping.";
  }

  identity tf-type {
    description
      "Identity for the traffic type.";
  }

  identity multicast-traffic {
    base tf-type;
    description
      "Identity for multicast traffic.";
  }

  identity broadcast-traffic {
    base tf-type;
    description
      "Identity for broadcast traffic.";
  }

  identity unknown-unicast-traffic {
    base tf-type;
    description
      "Identity for unknown unicast traffic.";
  }

  identity encapsulation-type {
    description
      "Identity for the encapsulation type.";
  }

  identity ethernet {
    base encapsulation-type;
    description
      "Identity for Ethernet type.";
  }

  identity vlan {
    base encapsulation-type;
    description
      "Identity for the VLAN type.";
  }

  identity eth-inf-type {
    description
      "Identity of the Ethernet interface type.";
  }

  identity tagged {
    base eth-inf-type;
    description
      "Identity of the tagged interface type.";
  }

  identity untagged {
    base eth-inf-type;
    description
      "Identity of the untagged interface type.";
  }

  identity lag {
    base eth-inf-type;
    description
      "Identity of the LAG interface type.";
  }

  identity l2vpn {
    base vpn-svc:service-type;
    description
      "Layer 2 VPN (L2VPN) service type.";
  }

  identity vpws {
    base l2vpn;
    description
      "Point-to-point Virtual Private Wire Service (VPWS)
       service type.";
  }

  identity pwe3 {
    base l2vpn;
    description
      "Pseudowire Emulation Edge to Edge (PWE3) service type.";
  }

  identity ldp-l2tp-vpls {
    base l2vpn;
    description
      "LDP-based or L2TP-based multipoint Virtual Private LAN
       Service (VPLS) service type.  This VPLS uses LDP-signaled
       Pseudowires or L2TP-signaled Pseudowires.";
  }

  identity bgp-vpls {
    base l2vpn;
    description
      "BGP-based multipoint VPLS service type.  This VPLS uses a
       BGP control plane as described in RFCs 4761 and 6624.";
  }

  identity vpws-evpn {
    base l2vpn;
    description
      "VPWS service type using Ethernet VPNs (EVPNs)
       as specified in RFC 7432.";
  }

  identity pbb-evpn {
    base l2vpn;
    description
      "Provider Backbone Bridge (PBB) service type using
       EVPNs as specified in RFC 7432.";
  }

  identity bundling-type {
    description
      "The base identity for the bundling type.  It supports
       multiple CE-VLANs associated with an L2VPN service or
       all CE-VLANs associated with an L2VPN service.";
  }

  identity multi-svc-bundling {
    base bundling-type;
    description
      "Identity for multi-service bundling, i.e.,
       multiple CE-VLAN IDs can be associated with an
       L2VPN service at a site.";
  }

  identity one2one-bundling {
    base bundling-type;
    description
      "Identity for one-to-one service bundling, i.e.,
       each L2VPN can be associated with only one CE-VLAN ID
       at a site.";
  }

  identity all2one-bundling {
    base bundling-type;
    description
      "Identity for all-to-one bundling, i.e., all CE-VLAN IDs
       are mapped to one L2VPN service.";
  }

  identity color-id {
    description
      "Base identity of the color ID.";
  }

  identity color-id-cvlan {
    base color-id;
    description
      "Identity of the color ID based on a CVLAN.";
  }

  identity cos-id {
    description
      "Identity of the CoS ID.";
  }

  identity cos-id-pcp {
    base cos-id;
    description
      "Identity of the CoS ID based on the
       Port Control Protocol (PCP).";
  }

  identity cos-id-dscp {
    base cos-id;
    description
      "Identity of the CoS ID based on DSCP.";
  }

  identity bum-type {
    description
      "Identity of the BUM type.";
  }

  identity broadcast {
    base bum-type;
    description
      "Identity of broadcast.";
  }

  identity unicast {
    base bum-type;
    description
      "Identity of unicast.";
  }

  identity multicast {
    base bum-type;
    description
      "Identity of multicast.";
  }

  identity loop-prevention-type {
    description
      "Identity of loop prevention.";
  }

  identity shut {
    base loop-prevention-type;
    description
      "Identity of shut protection.";
  }

  identity trap {
    base loop-prevention-type;
    description
      "Identity of trap protection.";
  }

  identity lacp-state {
    description
      "Identity of the LACP state.";
  }

  identity lacp-on {
    base lacp-state;
    description
      "Identity of LACP on.";
  }

  identity lacp-off {
    base lacp-state;
    description
      "Identity of LACP off.";
  }

  identity lacp-mode {
    description
      "Identity of the LACP mode.";
  }

  identity lacp-passive {
    base lacp-mode;
    description
      "Identity of LACP passive.";
  }

  identity lacp-active {
    base lacp-mode;
    description
      "Identity of LACP active.";
  }

  identity lacp-speed {
    description
      "Identity of the LACP speed.";
  }

  identity lacp-fast {
    base lacp-speed;
    description
      "Identity of LACP fast.";
  }

  identity lacp-slow {
    base lacp-speed;
    description
      "Identity of LACP slow.";
  }

  identity address-family {
    description
      "Identity for an address family.";
  }

  identity ipv4 {
    base address-family;
    description
      "Identity for an IPv4 address family.";
  }

  identity ipv6 {
    base address-family;
    description
      "Identity for an IPv6 address family.";
  }

  identity pm-type {
    description
      "Performance-monitoring type.";
  }

  identity loss {
    base pm-type;
    description
      "Loss measurement.";
  }

  identity delay {
    base pm-type;
    description
      "Delay measurement.";
  }

  identity fault-alarm-defect-type {
    description
      "Indicates the alarm-priority defect (i.e., the
       lowest-priority defect that is allowed to
       generate a fault alarm).";
  }

  identity remote-rdi {
    base fault-alarm-defect-type;
    description
      "Indicates the aggregate health
       of the Remote MEPs.";
  }

  identity remote-mac-error {
    base fault-alarm-defect-type;
    description
      "Indicates that one or more of the Remote MEPs are
       reporting a failure in their Port Status TLVs or
       Interface Status TLVs.";
  }

  identity remote-invalid-ccm {
    base fault-alarm-defect-type;
    description
      "Indicates that at least one of the Remote MEP
       state machines is not receiving valid
       Continuity Check Messages (CCMs) from its Remote MEP.";
  }

  identity invalid-ccm {
    base fault-alarm-defect-type;
    description
      "Indicates that one or more invalid CCMs have been
       received and that a period of time 3.5 times the length
       of those CCMs' transmission intervals has not yet expired.";
  }

  identity cross-connect-ccm {
    base fault-alarm-defect-type;
    description
      "Indicates that one or more cross-connect CCMs have been
       received and that 3.5 times the period of at least one of
       those CCMs' transmission intervals has not yet expired.";
  }

  identity frame-delivery-mode {
    description
      "Delivery types.";
  }

  identity discard {
    base frame-delivery-mode;
    description
      "Service frames are discarded.";
  }

  identity unconditional {
    base frame-delivery-mode;
    description
      "Service frames are unconditionally delivered to the
       destination site.";
  }

  identity unknown-discard {
    base frame-delivery-mode;
    description
      "Service frames are conditionally delivered to the
       destination site.  Packets with unknown destination addresses
       will be discarded.";
  }

  identity tagged-inf-type {
    description
      "Identity for the tagged interface type.";
  }

  identity priority-tagged {
    base tagged-inf-type;
    description
      "Identity for the priority-tagged interface.";
  }

  identity qinq {
    base tagged-inf-type;
    description
      "Identity for the QinQ tagged interface.";
  }

  identity dot1q {
    base tagged-inf-type;
    description
      "Identity for the dot1Q VLAN tagged interface.";
  }

  identity qinany {
    base tagged-inf-type;
    description
      "Identity for the QinAny tagged interface.";
  }

  identity vxlan {
    base tagged-inf-type;
    description
      "Identity for the VXLAN tagged interface.";
  }

  identity provision-model {
    description
      "Base identity for the provision model.";
  }

  identity single-side-provision {
    description
      "Identity for single-sided provisioning with discovery.";
  }

  identity doubled-side-provision {
    description
      "Identity for double-sided provisioning.";
  }

  identity mac-learning-mode {
    description
      "MAC learning mode.";
  }

  identity data-plane {
    base mac-learning-mode;
    description
      "User MAC addresses are learned through ARP broadcast.";
  }

  identity control-plane {
    base mac-learning-mode;
    description
      "User MAC addresses are advertised through EVPN-BGP.";
  }

  identity mac-action {
    description
      "Base identity for a MAC action.";
  }

  identity drop {
    base mac-action;
    description
      "Identity for dropping a packet.";
  }

  identity flood {
    base mac-action;
    description
      "Identity for packet flooding.";
  }

  identity warning {
    base mac-action;
    description
      "Identity for sending a warning log message.";
  }

  identity vxlan-peer-mode {
    description
      "Base identity for the VXLAN peer mode.";
  }

  identity static-mode {
    base vxlan-peer-mode;
    description
      "Identity for VXLAN access in the static mode.";
  }

  identity bgp-mode {
    base vxlan-peer-mode;
    description
      "Identity for VXLAN access by BGP EVPN learning.";
  }

  grouping flow-definition {
    leaf src-mac {
      type yang:mac-address;
      description
        "Source MAC.";
    }
    leaf dst-mac {
      type yang:mac-address;
      description
        "Destination MAC.";
    }
    description
      "Flow definition based on criteria.";
  }

  grouping site-acl {
    container access-control-list {
      if-feature "acl";
      list mac {
        key "mac-address";
        leaf mac-address {
          type yang:mac-address;
          description
            "MAC addresses.";
        }
        description
          "List of MAC addresses.";
      }
      description
        "Container for the ACL.";
    }
    description
      "Grouping that defines the ACL.";
  }

  grouping site-bum {
    container broadcast-unknown-unicast-multicast {
      if-feature "bum";
      leaf multicast-site-type {
        type enumeration {
          enum receiver-only {
            description
              "The site only has receivers.";
          }
          enum source-only {
            description
              "The site only has sources.";
          }
          enum source-receiver {
            description
              "The site has both sources and receivers.";
          }
        }
        default "source-receiver";
        description
          "Type of multicast site.";
      }
      list multicast-gp-address-mapping {
        key "id";
        leaf id {
          type uint16;
          description
            "Unique identifier for the mapping.";
        }
        leaf vlan-id {
          type uint16 {
            range "0..1024";
          }
          mandatory true;
          description
            "The VLAN ID of the multicast group.
             The range of the 12-bit VLAN ID is 0 to 1024.";
        }
        leaf mac-gp-address {
          type yang:mac-address;
          mandatory true;
          description
            "The MAC address of the multicast group.";
        }
        leaf port-lag-number {
          type uint32;
          description
            "The ports/LAGs belonging to the multicast group.";
        }
        description
          "List of port-to-group mappings.";
      }
      leaf bum-overall-rate {
        type uint64;
        units "bps";
        description
          "Overall rate for BUM.";
      }
      list bum-rate-per-type {
        key "type";
        leaf type {
          type identityref {
            base bum-type;
          }
          description
            "BUM type.";
        }
        leaf rate {
          type uint64;
          units "bps";
          description
            "Rate for BUM.";
        }
        description
          "List of limit rates for the BUM type.";
      }
      description
        "Container of BUM configurations.";
    }
    description
      "Grouping for BUM.";
  }

  grouping site-mac-loop-prevention {
    container mac-loop-prevention {
      if-feature "mac-loop-prevention";
      leaf protection-type {
        type identityref {
          base loop-prevention-type;
        }
        default "trap";
        description
          "Protection type.  By default, the protection
           type is 'trap'.";
      }
      leaf frequency {
        type uint32;
        default "5";
        description
          "The number of times to detect MAC duplication, where
           a 'duplicate MAC address' situation has occurred and
           the duplicate MAC address has been added to a list of
           duplicate MAC addresses.  By default, the number of
           times is 5.";
      }
      leaf retry-timer {
        type uint32;
        units "seconds";
        description
          "The retry timer.  When the retry timer expires,
           the duplicate MAC address will be flushed from
           the MAC-VRF.";
      }
      description
        "Container of MAC loop-prevention parameters.";
    }
    description
      "Grouping for MAC loop prevention.";
  }

  augment "/svc:svc/svc:svc-profiles"
        + "/svc:valid-provider-identifiers" {
    list remote-carrier-identifier {
      key "id";
      leaf id {
        type string;
        description
          "Identification of the remote carrier name to be used.
           It can be an L2VPN partner, data-center SP, or
           private CSP.  Local to each administration.";
      }
      description
        "List for Remote Carrier Identifiers.";
    }
  }

  augment "/svc:svc/vpn-svc:vpn-services/vpn-svc:vpn-service" {
    container frame-delivery {
      if-feature "bum";
      container customer-tree-flavors {
        leaf-list tree-flavor {
          type identityref {
            base multicast-tree-type;
          }
          description
            "Type of tree to be used.";
        }
        description
          "Types of trees used by the customer.";
      }
      container bum-deliveries {
        list bum-delivery {
          key "frame-type";
          leaf frame-type {
            type identityref {
              base tf-type;
            }
            description
              "Type of frame delivery.  It supports unicast
               frame delivery, multicast frame delivery,
               and broadcast frame delivery.";
          }
          leaf delivery-mode {
            type identityref {
              base frame-delivery-mode;
            }
            default "unconditional";
            description
              "Defines the frame delivery mode
               ('unconditional' (default), 'conditional',
               or 'discard').  By default, service frames are
               unconditionally delivered to the destination site.";
          }
          description
            "List of frame delivery types and modes.";
        }
        description
          "Defines the frame delivery types and modes.";
      }
      leaf multicast-gp-port-mapping {
        type identityref {
          base multicast-gp-address-mapping;
        }
        description
          "Describes the way in which each interface is
           associated with the multicast group.";
      }
      description
        "Multicast global parameters for the VPN service.";
    }
  }

  augment "/svc:svc/svc:sites/svc:site" {
    uses site-bum;
    uses site-mac-loop-prevention;
    uses site-acl;
    leaf bundling-type {
      type identityref {
        base bundling-type;
      }
      default "one2one-bundling";
      description
        "Bundling type.  By default, each L2VPN
          can be associated with only one
          CE-VLAN, i.e., one-to-one bundling is used.";
    }
    leaf default-ce-vlan-id {
      type uint32;
      description
        "Default CE VLAN ID set at the site level.";
    }
  }

  augment "/svc:svc/svc:sites/svc:site/svc:service"
        + "/svc:qos/svc:qos-classification-policy"
        + "/svc:rule/svc:match-type/svc:match-flow"
        + "/svc:match-flow" {
    uses flow-definition;
  }

  augment "/svc:svc/svc:sites/svc:site/svc:site-network-accesses"
        + "/svc:site-network-access" {
    leaf remote-carrier-name {
      when "derived-from-or-self(../../../vpn-svc:site-vpn-flavor,"
         + "'vpn-svc:site-vpn-flavor-nni')" {
        description
          "Relevant when the site's VPN flavor is
           'site-vpn-flavor-nni'.";
      }
      type leafref {
        path "/svc:svc/svc:svc-profiles/"
           + "svc:valid-provider-identifiers"
           + "/remote-carrier-identifier/id";
      }
      description
        "Remote carrier name.  The 'remote-carrier-name'
         parameter must be configured only when
         'site-vpn-flavor' is set to 'site-vpn-flavor-nni'.
         If it is not set, it indicates that the customer
         does not know the remote carrier's name
         beforehand.";
    }
    container connection {
      leaf encapsulation-type {
        type identityref {
          base encapsulation-type;
        }
        default "ethernet";
        description
          "Encapsulation type.  By default, the
           encapsulation type is set to 'ethernet'.";
      }
      leaf eth-inf-type {
        type identityref {
          base eth-inf-type;
        }
        default "untagged";
        description
          "Ethernet interface type.  By default, the
           Ethernet interface type is set to 'untagged'.";
      }
      container tagged-interface {
        leaf type {
          type identityref {
            base tagged-inf-type;
          }
          default "priority-tagged";
          description
            "Tagged interface type.  By default,
             the type of the tagged interface is
             'priority-tagged'.";
        }
        container dot1q-vlan-tagged {
          when "derived-from-or-self(../type, "
             + "'l2vpn-svc:dot1q')" {
            description
              "Only applies when the type of the tagged
               interface is 'dot1q'.";
          }
          if-feature "dot1q";
          leaf tg-type {
            type identityref {
              base tag-type;
            }
            default "c-vlan";
            description
              "Tag type.  By default, the tag type is
               'c-vlan'.";
          }
          leaf cvlan-id {
            type uint16;
            description
              "VLAN identifier.";
          }
          description
            "Tagged interface.";
        }
        container priority-tagged {
          when "derived-from-or-self(../type, "
             + "'l2vpn-svc:priority-tagged')" {
            description
              "Only applies when the type of the tagged
               interface is 'priority-tagged'.";
          }
          leaf tag-type {
            type identityref {
              base tag-type;
            }
            default "c-vlan";
            description
              "Tag type.  By default, the tag type is
               'c-vlan'.";
          }
          description
            "Priority tagged.";
        }
        container qinq {
          when "derived-from-or-self(../type, "
             + "'l2vpn-svc:qinq')" {
            description
              "Only applies when the type of the tagged
               interface is 'qinq'.";
          }
          if-feature "qinq";
          leaf tag-type {
            type identityref {
              base tag-type;
            }
            default "c-s-vlan";
            description
              "Tag type.  By default, the tag type is
               'c-s-vlan'.";
          }
          leaf svlan-id {
            type uint16;
            description
              "SVLAN identifier.";
          }
          leaf cvlan-id {
            type uint16;
            description
              "CVLAN identifier.";
          }
          description
            "QinQ.";
        }
        container qinany {
          when "derived-from-or-self(../type, "
             + "'l2vpn-svc:qinany')" {
            description
              "Only applies when the type of the tagged
               interface is 'qinany'.";
          }
          if-feature "qinany";
          leaf tag-type {
            type identityref {
              base tag-type;
            }
            default "s-vlan";
            description
              "Tag type.  By default, the tag type is
               's-vlan'.";
          }
          leaf svlan-id {
            type uint16;
            description
              "SVLAN ID.";
          }
          description
            "Container for QinAny.";
        }
        container vxlan {
          when "derived-from-or-self(../type, "
             + "'l2vpn-svc:vxlan')" {
            description
              "Only applies when the type of the tagged
               interface is 'vxlan'.";
          }
          if-feature "vxlan";
          leaf vni-id {
            type uint32;
            description
              "VXLAN Network Identifier (VNI).";
          }
          leaf peer-mode {
            type identityref {
              base vxlan-peer-mode;
            }
            default "static-mode";
            description
              "Specifies the VXLAN access mode.  By default,
               the peer mode is set to 'static-mode'.";
          }
          list peer-list {
            key "peer-ip";
            leaf peer-ip {
              type inet:ip-address;
              description
                "Peer IP.";
            }
            description
              "List of peer IP addresses.";
          }
          description
            "QinQ.";
        }
        description
          "Container for tagged interfaces.";
      }
      container untagged-interface {
        leaf speed {
          type uint32;
          units "mbps";
          default "10";
          description
            "Port speed.";
        }
        leaf mode {
          type neg-mode;
          default "auto-neg";
          description
            "Negotiation mode.";
        }
        leaf phy-mtu {
          type uint32;
          units "bytes";
          description
            "PHY MTU.";
        }
        leaf lldp {
          type boolean;
          default "false";
          description
            "LLDP.  Indicates that LLDP is supported.";
        }
        container oam-802.3ah-link {
          if-feature "oam-3ah";
          leaf enabled {
            type boolean;
            default "false";
            description
              "Indicates whether or not to support
               OAM 802.3ah links.";
          }
          description
            "Container for OAM 802.3ah links.";
        }
        leaf uni-loop-prevention {
          type boolean;
          default "false";
          description
            "If this leaf is set to 'true', then the port
             automatically goes down when a physical
             loopback is detected.";
        }
        description
          "Container of untagged interface attribute
           configurations.";
      }
      container lag-interfaces {
        if-feature "lag-interface";
        list lag-interface {
          key "index";
          leaf index {
            type string;
            description
              "LAG interface index.";
          }
          container lacp {
            if-feature "lacp";
            leaf enabled {
              type boolean;
              default "false";
              description
                "LACP on/off.  By default, LACP is disabled.";
            }
            leaf mode {
              type neg-mode;
              description
                "LACP mode.  LACP modes have active mode and
                 passive mode ('false').  'Active mode' means
                 initiating the auto-speed negotiation and
                 trying to form an Ethernet channel with the
                 other end.  'Passive mode' means not initiating
                 the negotiation but responding to LACP packets
                 initiated by the other end (e.g., full duplex
                 or half duplex).";
            }
            leaf speed {
              type uint32;
              units "mbps";
              default "10";
              description
                "LACP speed.  By default, the LACP speed is 10
                 Mbps.";
            }
            leaf mini-link-num {
              type uint32;
              description
                "Defines the minimum number of links that must
                 be active before the aggregating link is put
                 into service.";
            }
            leaf system-priority {
              type uint16;
              default "32768";
              description
                "Indicates the LACP priority for the system.
                 The range is from 0 to 65535.
                 The default is 32768.";
            }
            container micro-bfd {
              if-feature "micro-bfd";
              leaf enabled {
                type enumeration {
                  enum on {
                    description
                      "Micro-bfd on.";
                  }
                  enum off {
                    description
                      "Micro-bfd off.";
                  }
                }
                default "off";
                description
                  "Micro-BFD on/off.  By default, micro-BFD
                   is set to 'off'.";
              }
              leaf interval {
                type uint32;
                units "milliseconds";
                description
                  "BFD interval.";
              }
              leaf hold-timer {
                type uint32;
                units "milliseconds";
                description
                  "BFD hold timer.";
              }
              description
                "Container of micro-BFD configurations.";
            }
            container bfd {
              if-feature "bfd";
              leaf enabled {
                type boolean;
                default "false";
                description
                  "BFD activation.  By default, BFD is not
                   activated.";
              }
              choice holdtime {
                default "fixed";
                case profile {
                  leaf profile-name {
                    type leafref {
                      path "/svc:svc/svc:svc-profiles/"
                         + "svc:valid-provider-identifiers"
                         + "/svc:bfd-profile-identifier/svc:id";
                    }
                    description
                      "SP well-known profile.";
                  }
                  description
                    "SP well-known profile.";
                }
                case fixed {
                  leaf fixed-value {
                    type uint32;
                    units "milliseconds";
                    description
                      "Expected hold time expressed in
                       milliseconds.";
                  }
                }
                description
                  "Choice for the hold-time flavor.";
              }
              description
                "Container for BFD.";
            }
            container member-links {
              list member-link {
                key "name";
                leaf name {
                  type string;
                  description
                    "Member link name.";
                }
                leaf speed {
                  type uint32;
                  units "mbps";
                  default "10";
                  description
                    "Port speed.";
                }
                leaf mode {
                  type neg-mode;
                  default "auto-neg";
                  description
                    "Negotiation mode.";
                }
                leaf link-mtu {
                  type uint32;
                  units "bytes";
                  description
                    "Link MTU size.";
                }
                container oam-802.3ah-link {
                  if-feature "oam-3ah";
                  leaf enabled {
                    type boolean;
                    default "false";
                    description
                      "Indicates whether OAM 802.3ah links are
                       supported.";
                  }
                  description
                    "Container for OAM 802.3ah links.";
                }
                description
                  "Member link.";
              }
              description
                "Container of the member link list.";
            }
            leaf flow-control {
              type boolean;
              default "false";
              description
                "Flow control.  Indicates whether flow control
                 is supported.";
            }
            leaf lldp {
              type boolean;
              default "false";
              description
                "LLDP.  Indicates whether LLDP is supported.";
            }
            description
              "LACP.";
          }
          description
            "List of LAG interfaces.";
        }
        description
          "Container of LAG interface attribute
           configurations.";
      }
      list cvlan-id-to-svc-map {
        key "svc-id";
        leaf svc-id {
          type leafref {
            path "/svc:svc/vpn-svc:vpn-services"
               + "/vpn-svc:vpn-service/vpn-svc:vpn-id";
          }
          description
            "VPN service identifier.";
        }
        list cvlan-id {
          key "vid";
          leaf vid {
            type uint16;
            description
              "CVLAN ID.";
          }
          description
            "List of CVLAN-ID-to-SVC-map configurations.";
        }
        description
          "List of CVLAN-ID-to-L2VPN-service-map
           configurations.";
      }
      container l2cp-control {
        if-feature "l2cp-control";
        leaf stp-rstp-mstp {
          type control-mode;
          description
            "STP / Rapid STP (RSTP) / Multiple STP (MSTP)
             protocol type applicable to all sites.";
        }
        leaf pause {
          type control-mode;
          description
            "Pause protocol type applicable to all sites.";
        }
        leaf lacp-lamp {
          type control-mode;
          description
            "LACP / Link Aggregation Marker Protocol (LAMP).";
        }
        leaf link-oam {
          type control-mode;
          description
            "Link OAM.";
        }
        leaf esmc {
          type control-mode;
          description
            "Ethernet Synchronization Messaging Channel
             (ESMC).";
        }
        leaf l2cp-802.1x {
          type control-mode;
          description
            "IEEE 802.1x.";
        }
        leaf e-lmi {
          type control-mode;
          description
            "E-LMI.";
        }
        leaf lldp {
          type boolean;
          description
            "LLDP protocol type applicable to all sites.";
        }
        leaf ptp-peer-delay {
          type control-mode;
          description
            "Precision Time Protocol (PTP) peer delay.";
        }
        leaf garp-mrp {
          type control-mode;
          description
            "GARP/MRP.";
        }
        description
          "Container of L2CP control configurations.";
      }
      container oam {
        if-feature "ethernet-oam";
        leaf md-name {
          type string;
          description
            "Maintenance domain name.";
        }
        leaf md-level {
          type uint16 {
            range "0..255";
          }
          description
            "Maintenance domain level.  The level may be
             restricted in certain protocols (e.g.,
             protocols in Layer 0 to Layer 7).";
        }
        list cfm-8021-ag {
          if-feature "cfm";
          key "maid";
          leaf maid {
            type string;
            description
              "Identifies a Maintenance Association (MA).";
          }
          leaf mep-id {
            type uint32;
            description
              "Local Maintenance Entity Group End Point (MEP)
               ID.  The non-existence of this leaf means
               that no defects are to be reported.";
          }
          leaf mep-level {
            type uint32;
            description
              "Defines the MEP level.  The non-existence of this
               leaf means that no defects are to be reported.";
          }
          leaf mep-up-down {
            type enumeration {
              enum up {
                description
                  "MEP up.";
              }
              enum down {
                description
                  "MEP down.";
              }
            }
            default "up";
            description
              "MEP up/down.  By default, MEP up is used.
               The non-existence of this leaf means that
               no defects are to be reported.";
          }
          leaf remote-mep-id {
            type uint32;
            description
              "Remote MEP ID.  The non-existence of this leaf
               means that no defects are to be reported.";
          }
          leaf cos-for-cfm-pdus {
            type uint32;
            description
              "CoS for CFM PDUs.  The non-existence of this leaf
               means that no defects are to be reported.";
          }
          leaf ccm-interval {
            type uint32;
            units "milliseconds";
            default "10000";
            description
              "CCM interval.  By default, the CCM interval is
               10,000 milliseconds (10 seconds).";
          }
          leaf ccm-holdtime {
            type uint32;
            units "milliseconds";
            default "35000";
            description
              "CCM hold time.  By default, the CCM hold time
               is 3.5 times the CCM interval.";
          }
          leaf alarm-priority-defect {
            type identityref {
              base fault-alarm-defect-type;
            }
            default "remote-invalid-ccm";
            description
              "The lowest-priority defect that is
               allowed to generate a fault alarm.  By default,
               'fault-alarm-defect-type' is set to
               'remote-invalid-ccm'.  The non-existence of
               this leaf means that no defects are
               to be reported.";
          }
          leaf ccm-p-bits-pri {
            type ccm-priority-type;
            description
              "The priority parameter for CCMs transmitted by
               the MEP.  The non-existence of this leaf means
               that no defects are to be reported.";
          }
          description
            "List of 802.1ag CFM attributes.";
        }
        list y-1731 {
          if-feature "y-1731";
          key "maid";
          leaf maid {
            type string;
            mandatory true;
            description
              "Identifies an MA.";
          }
          leaf mep-id {
            type uint32;
            description
              "Local MEP ID.  The non-existence of this leaf
               means that no measurements are to be reported.";
          }
          leaf type {
            type identityref {
              base pm-type;
            }
            default "delay";
            description
              "Performance-monitoring types.  By default, the
               performance-monitoring type is set to 'delay'.
               The non-existence of this leaf means that no
               measurements are to be reported.";
          }
          leaf remote-mep-id {
            type uint32;
            description
              "Remote MEP ID.  The non-existence of this
               leaf means that no measurements are to be
               reported.";
          }
          leaf message-period {
            type uint32;
            units "milliseconds";
            default "10000";
            description
              "Defines the interval between Y.1731
               performance-monitoring messages.  The message
               period is expressed in milliseconds.";
          }
          leaf measurement-interval {
            type uint32;
            units "seconds";
            description
              "Specifies the measurement interval for
               statistics.  The measurement interval is
               expressed in seconds.";
          }
          leaf cos {
            type uint32;
            description
              "CoS.  The non-existence of this leaf means that
               no measurements are to be reported.";
          }
          leaf loss-measurement {
            type boolean;
            default "false";
            description
              "Indicates whether or not to enable loss
               measurement.  By default, loss
               measurement is not enabled.";
          }
          leaf synthetic-loss-measurement {
            type boolean;
            default "false";
            description
              "Indicates whether or not to enable synthetic loss
               measurement.  By default, synthetic loss
               measurement is not enabled.";
          }
          container delay-measurement {
            leaf enable-dm {
              type boolean;
              default "false";
              description
                "Indicates whether or not to enable delay
                 measurement.  By default, delay measurement
                 is not enabled.";
            }
            leaf two-way {
              type boolean;
              default "false";
              description
                "Indicates whether delay measurement is two-way
                 ('true') or one-way ('false').  By default,
                 one-way measurement is enabled.";
            }
            description
              "Container for delay measurement.";
          }
          leaf frame-size {
            type uint32;
            units "bytes";
            description
              "Frame size.  The non-existence of this leaf
               means that no measurements are to be reported.";
          }
          leaf session-type {
            type enumeration {
              enum proactive {
                description
                  "Proactive mode.";
              }
              enum on-demand {
                description
                  "On-demand mode.";
              }
            }
            default "on-demand";
            description
              "Session type.  By default, the session type
               is 'on-demand'.  The non-existence of this
               leaf means that no measurements are to be
               reported.";
          }
          description
            "List of configured Y-1731 instances.";
        }
        description
          "Container for Ethernet Service OAM.";
      }
      description
        "Container for connection requirements.";
    }
    container availability {
      leaf access-priority {
        type uint32;
        default "100";
        description
          "Access priority.  The higher the access-priority
           value, the higher the preference will be for the
           access in question.";
      }
      choice redundancy-mode {
        case single-active {
          leaf single-active {
            type empty;
            description
              "Single-active mode.";
          }
          description
            "In single-active mode, only one node forwards
             traffic to and from the Ethernet segment.";
        }
        case all-active {
          leaf all-active {
            type empty;
            description
              "All-active mode.";
          }
          description
            "In all-active mode, all nodes can forward
             traffic.";
        }
        description
          "Redundancy mode choice.";
      }
      description
        "Container of available optional configurations.";
    }
    uses site-bum;
    uses site-mac-loop-prevention;
    uses site-acl;
    container mac-addr-limit {
      if-feature "mac-addr-limit";
      leaf limit-number {
        type uint16;
        default "2";
        description
          "Maximum number of MAC addresses learned from
           the subscriber for a single service instance.
           The default allowed maximum number of MAC
           addresses is 2.";
      }
      leaf time-interval {
        type uint32;
        units "seconds";
        default "300";
        description
          "The aging time of the MAC address.  By default,
           the aging time is set to 300 seconds.";
      }
      leaf action {
        type identityref {
          base mac-action;
        }
        default "warning";
        description
          "Specifies the action taken when the upper limit is
           exceeded: drop the packet, flood the packet, or
           simply send a warning log message.  By default,
           the action is set to 'warning'.";
      }
      description
        "Container of MAC address limit configurations.";
    }
  }

  augment "/svc:svc/svc:sites/svc:site/svc:site-network-accesses"
        + "/svc:site-network-access/svc:service/svc:qos"
        + "/svc:qos-classification-policy/svc:rule"
        + "/svc:match-type/svc:match-flow"
        + "/svc:match-flow" {
    uses flow-definition;
  }
}
